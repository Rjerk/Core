(defun C:pentagram()
    (setq osmd (getvar "osmode"))
    (setq colr (getvar "cecolor"))
    (setq cen (getpoint "select circle's center"))
    (setq rad (getreal "enter circle's radius"))
    (setvar "CEcolor" "red")
    (command "circle" cen rad)
    (command "hatch" "solid" "L" "")
    (setq d (* pi 0.2))
    (setq a (/ pi 10))
    (setq rad_in (* rad (/ (sin (/ pi 10)) (cos (/ pi 5)))))
    (setq p1 (polar cen a rad))
    (setq p2 (polar cen (+ a d) rad_in))
    (setq p3 (polar cen (+ a (* 2 d)) rad))
    (setq p4 (polar cen (+ a (* 3 d)) rad_in))
    (setq p5 (polar cen (+ a (* 4 d)) rad))
    (setq p6 (polar cen (+ a (* 5 d)) rad_in))
    (setq p7 (polar cen (+ a (* 6 d)) rad))
    (setq p8 (polar cen (+ a (* 7 d)) rad_in))
    (setq p9 (polar cen (+ a (* 8 d)) rad))
    (setq p10 (polar cen (+ a (* 9 d)) rad_in))
    (setvar "CEcolor" "white")
    (command "pline" p1 p2 p3 p4 p5 p6 p7 p8 p9 p10 "c")
    (command "hatch" "solid" "L" "")
    (setvar "osmode" osmd)
    (setvar "cecolor" colr)
    (prin1)
)
