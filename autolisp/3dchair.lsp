(defun C:3dchair()
    (setq osmd (getvar "osmode"))
    (setq colr (getvar "cecolor"))

    (setvar "CEcolor" "red")
    (command "view" "seiso")
    (command "box" "400,300" "@100,-100" 700)
    (command "ucs" "zaxis" "500,200,0" "500,-100,0")
    (setq p1 "0,10,-30") (setq p2 "@250,0") (setq p3 "@0,-10")
    (setq p4 "@50,0") (setq p5 "@0,50") (setq p6 "@-300,40")
    (command "pline" p1 p2 p3 p4 p5 p6 "c")
    (command "extrude" 1 "" "d" "0,0,0" "0,0,-40")
    (command "ucs" "x" 90)
    (prompt "choose the chair legs.")
    (setq chair (ssget))
    (command "array" chair "" "p" "-50,-50" 4 360 "y")
    (command "box" "350,350,-700" "@-800,-800,0" -40)
    (command "union" (ssget "X") "")
    (command "render")
    (setq chair nil)

    (setvar "osmode" osmd)
    (setvar "cecolor" colr)
    (prin1)
)
