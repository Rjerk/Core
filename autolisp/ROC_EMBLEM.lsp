(defun C:roc()
    (setq osmd (getvar "osmode")) (setq colr (getvar "cecolor"))
    (setq cen (getpoint "POSITION: "))
    (setq rad (getreal "RADIUS: "))
    (setvar "CEcolor" "blue")  (setq d (/ pi 6))
    (command "circle" cen rad) (command "hatch" "solid" "L" "")
    (setq p1 (polar cen 0 rad)) (setq p2 (polar cen (* d 1) rad))
    (setq p3 (polar cen (* d 2) rad)) (setq p4 (polar cen (* d 3) rad))
    (setq p5 (polar cen (* d 4) rad)) (setq p6 (polar cen (* d 5) rad))
    (setq p7 (polar cen (* d 6) rad)) (setq p8 (polar cen (* d 7) rad))
    (setq p9 (polar cen (* d 8) rad)) (setq p10 (polar cen (* d 9) rad))
    (setq p11 (polar cen (* d 10) rad)) (setq p12 (polar cen (* d 11) rad))
    (setvar "CEcolor" "red")
    (command "pline" p1 p6 p11 p4 p9 p2 p7 p12 p5 p10 p3 p8 "c")
    (command "hatch" "solid" "L" "")
    (setvar "CEcolor" "blue") (command "circle" cen (/ rad 1.75))
    (command "hatch" "solid" "L" "")
    (setvar "CEcolor" "red") (command "circle" cen (/ (* rad 52) 105))
    (command "hatch" "solid" "L" "")
    (setvar "osmode" osmd) (setvar "cecolor" colr)
)
