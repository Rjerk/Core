(defun c:5test1()
  (setq pa (getpoint "enter left-corner pointer:"))
  (setq ww (getreal "\nenter bottom length:"))
  (setq kk (getreal "\nenter right length:"))
  (setq pb (polar pa 0 ww))
  (setq hh (sqrt (- (* kk kk) (* ww ww))))
  (setq pc (polar pa (/ pi 2) hh))
  (command "line" pa pb pc "c")
  (princ "\n another hh length=")(print hh)

  (setq ang_pb (atan (/ hh ww)))
  (setq ang_pb (* ang_pb (/ 180 pi)))
  (setq ang_pc (- 90 ang_pb))
  (princ "\nPB = ")(princ ang_pb)(princ " angle")
  (princ "\nPC = ")(princ ang_pc)(princ " angle")
  (prin1)
)
