(defun C:3dkettle()
    (setq osmd (getvar "osmode"))
    (setq colr (getvar "cecolor"))
    (setvar "CEcolor" "red")
    (command "view" "neiso")
    (command "pline" "240,210" "@0,-130" "a" "@70,0" "l" "@0,130" "a" "l" "a" "cl" "")
    (command "extrude" (ssget "X") "" 160)
    (command "ucs" "zaxis" "275,245,0" "276,245,0")
    (command "pline" "0,60,0" "@160<60" "")
    (command "ucs" "zaxis" "0,60,0" "80,200,0")
    (command "circle" "0,0,0" 10)
    ;(prompt "选择圆形壶口，然后按Enter")
    (command "extrude" (ssget) "" 160)
    ;(prompt "选择壶嘴，然后按Enter")
    (command "solidedit" "face" "taper" (ssget) "" "0,0,0" "@0,0,160" 0.5 "X" "X")
    (command "union" (ssget "X") "")
    ;(prompt "选择壶身，然后按Enter")
    (command "solidedit" "body" "shell" (ssget) "" 2 "X" "X")
    (command "ucs" "zaxis" "-9.0909,219.8798,0" "-166.3931,219.8798,0")
    (command "ucs" "x" -90)
    (command "ucs" "z" -90)
    (command "pline" "20,80,0" "@0,-45" "a" "@-40,0" "l" "@0,45" "c")
    ;(prompt "选择壶上的口子，然后按Enter")
    (command "extrude" (ssget) "" -30)
    (command "box" "-35,165,0" "@70,200,50")
    ;(prompt "选择壶身后按Enter, 然后选择长方体和壶身上的小口按Enter")
    (command "subtract" (ssget) "" (ssget) "")
    (command "3dpoly" "20,120,0" "@0,0,20" "@-40,0" "@0,0,-20" "@3,0" "@0,0,17" "@34,0" "@0,0,-17" "c")
    ;(prompt "选择提手，然后按Enter")
    (command "extrude" (ssget) "" -15)
    (command "union" (ssget "X") "")
    (command "render")
    (setvar "osmode" osmd)
    (setvar "cecolor" colr)
    (prin1)
)
